module nsf-facing-interface {
  namespace 
    "http://skku.edu/nsf-facing-interface";
  prefix
    nsf-facing-interface;

  import ietf-inet-types{
    prefix inet;
  }
  import ietf-yang-types{
    prefix yang;
  }
  import tailf-xsd-types {
	  prefix xs;
  }
  
  organization
    "IETF I2NSF (Interface to Network Security Functions) 
     Working Group";

  contact
    "WG Web: <http://tools.ietf.org/wg/i2nsf>
     WG List: <mailto:i2nsf@ietf.org>

     WG Chair: Adrian Farrel
     <mailto:Adrain@olddog.co.uk>

     WG Chair: Linda Dunbar
     <mailto:Linda.duhbar@huawei.com>

     Editor: Jingyong Tim Kim 
     <mailto:wlsdyd0930@nate.com>
    
     Editor: Jaehoon Paul Jeong
     <mailto:pauljeong@skku.edu>
     
     Editor: Susan Hares
     <mailto:shares@ndzh.com>";

  description
    "This module defines a YANG data module for network security 
     functions.";
  revision "2017-07-03"{
    description "The second revision";
    reference
      "draft-xibassnez-i2nsf-capability-01;
       draft-kim-i2nsf-nsf-facing-interface-data-model-02";
  }

  typedef sec-event-format {
      type enumeration {
        enum unknown {
            description
              "If usrSecEventFormat is unknown";
        }
        enum guid {
            description
              "If usrSecEventFormat is GUID 
              (Generic Unique IDentifier)";
        }
        enum uuid {
            description
              "If usrSecEventFormat is UUID 
              (Universal Unique IDentifier)";
        }
        enum uri {
            description
              "If usrSecEventFormat is URI 
              (Uniform Resource Identifier)";
        }
        enum fqdn {
            description
              "If usrSecEventFormat is FQDN 
              (Fully Qualified Domain Name)";
        }
        enum fqpn {
            description
              "If usrSecEventFormat is FQPN 
              (Fully Qualified Path Name)";
        }
      }
      description
        "This is used for SecEventFormat.";
  }

  typedef ingress-action {
      type enumeration {
        enum pass {
            description
              "If ingress action is pass";
        }
        enum drop {
            description
              "If ingress action is drop";
        }
        enum reject {
            description
              "If ingress action is reject";
        }
        enum alert {
            description
              "If ingress action is alert";
        }
        enum mirror {
            description
              "If ingress action is mirror";
        }
      }
      description
        "This is used for ingress action.";
  }

  typedef egress-action {
      type enumeration {
        enum invoke-signaling {
            description
              "If egress action is invoke signaling";
        }
        enum tunnel-encapsulation {
            description
              "If egress action is tunnel encapsulation";
        }
        enum forwarding {
            description
              "If egress action is forwarding";
        }
        enum redirection {
            description
              "If egress action is redirection";
        }
      }
      description
        "This is used for egress action.";
  }


  //Groupings

 container cfg-network-security-control {
  description
    "Configuration for Network Security Control.";

  list policy {
    key "policy-id";
    description
      "policy is a grouping
       including a set of security rules according to certain logic, 
       i.e., their similarity or mutual relations, etc. The network
       security policy is able to apply over both the unidirectional
       and bidirectional traffic across the NSF.";
      
      leaf policy-name {
        type string;
        mandatory true;
        description
          "The name of the policy. 
           This must be unique.";
      }

      leaf policy-id {
        type uint8;
        mandatory true;
        description
          "The ID of the policy.
           This must be unique.";     
      }
      
      list rules {
        key "rule-id";
        description
          "This is a rule for network security control.";
          
          leaf rule-name {
            type string;
            mandatory true;
            description
              "The name of the rule.
               This must be unique.";
          }
          
          leaf rule-id {
            type uint32;
            mandatory true;
            description
              "The ID of the rule.
               This is key for rule-list.
               This must be unique.";
          }

          leaf rule-msg {
            type string;
            description
              "The keyword msg gives more information about 
               the signature and the possible alert.";
          }

          leaf rule-rev {
            type uint8;
            description
              "The sid keyword is almost every time 
               accompanied by reb.";
          }

          leaf rule-gid {
            type uint8;
            description
              "The gid keyword can be used to give different 
               groups of signatures another id value 
               (like in sid)..";
          }

          leaf rule-class-type {
            type string;
            description
              "The classtype keyword gives information about 
               the classification of rules and alerts.";
          }

          leaf rule-reference {
            type string;
            description
              "The reference keywords direct to places where 
               information about the signature and about 
               the problem the signature tries to address, 
               can be found.";
          }

          leaf rule-priority {
            type uint8;
            description
              "The priority keyword comes with a mandatory 
               numeric value which can range from 1 till 255.";
          }
          
          container event {
            description 
              " An event is defined as any important occurrence in time 
                of a change in the system being managed, and/or in the 
                environment of the system being managed. When used in 
                the context of policy rules for a flow-based NSF, it is 
                used to determine whether the Condition clause of the 
                Policy Rule can be evaluated or not. Examples of an 
                I2NSF event include time and user actions (e.g., logon,
                logoff, and actions that violate any ACL.).";

              list user-security-event {
                key usr-sec-event-id;
                description
                  "The purpose of this class is to represent events that
                   are initiated by a user, such as logon and logoff 
                   events. Information in this event may be used as part
                   of a test to determine if the Condition clause in 
                   this ECA Policy Rule should be evaluated or not. 
                   Examples include user identification data and the 
                   type of connection used by the user.";

                leaf usr-sec-event-id {
                  type uint8;
                  mandatory true;
                  description
                    "The ID of the usr-sec-event.
                     This is key for usr-sec-event-list.
                     This must be unique.";
                }
                
                leaf usr-sec-event-content {
                  type string;
                  mandatory true;
                  description
                   "This is a mandatory string that contains the content 
                    of the UserSecurityEvent. The format of the content 
                    is specified in the usrSecEventFormat class 
                    attribute, and the type of event is defined in the 
                    usrSecEventType class attribute. An example of the 
                    usrSecEventContent attribute is a string hrAdmin,
                    with the usrSecEventFormat set to 1 (GUID) and the 
                    usrSecEventType attribute set to 5 (new logon).";
                }
                
                leaf usr-sec-event-format {
                  type sec-event-format;
                  mandatory true;
                  description
                   "This is a mandatory uint 8 enumerated integer, which 
                    is used to specify the data type of the 
                    usrSecEventContent attribute. The content is 
                    specified in the usrSecEventContent class attribute, 
                    and the type of event is defined in the 
                    usrSecEventType class attribute. An example of the 
                    usrSecEventContent attribute is string hrAdmin, 
                    with the usrSecEventFormat attribute set to 1 (GUID) 
                    and the usrSecEventType attribute set to 5 
                    (new logon).";
                }
                
                leaf usr-sec-event-type {
                  type enumeration {
                      enum unknown {
                          description
                            "If usrSecEventType is unknown";
                      }
                      enum user-created {
                          description
                            "If usrSecEventType is new user 
                            created";
                      }
                      enum user-grp-created {
                          description
                            "If usrSecEventType is new user 
                            group created";
                      }
                      enum user-deleted {
                          description
                            "If usrSecEventType is user 
                            deleted";
                      }
                      enum user-grp-deleted {
                          description
                            "If usrSecEventType is user 
                            group deleted";
                      }
                      enum user-logon {
                          description
                            "If usrSecEventType is user 
                            logon";
                      }
                      enum user-logoff {
                          description
                            "If usrSecEventType is user 
                            logoff";
                      }
                      enum user-access-request {
                          description
                            "If usrSecEventType is user 
                            access request";
                      }
                      enum user-access-granted {
                          description
                            "If usrSecEventType is user 
                            granted";
                      }
                      enum user-access-violation {
                          description
                            "If usrSecEventType is user 
                            violation";
                      }
                  }
                  mandatory true;
                  description
                   "This is a mandatory uint 8 enumerated integer, which 
                    is used to specify the type of event that involves 
                    this user. The content and format are specified in 
                    the usrSecEventContent and usrSecEventFormat class 
                    attributes, respectively. An example of the 
                    usrSecEventContent attribute is string hrAdmin, 
                    with the usrSecEventFormat attribute set to 1 (GUID) 
                    and the usrSecEventType attribute set to 5 
                   (new logon).";
                }
              }
              
              list device-security-event {
                key dev-sec-event-id;
                description
                 "The purpose of a DeviceSecurityEvent is to represent 
                  events that provide information from the Device that 
                  are important to I2NSF Security. Information in this 
                  event may be used as part of a test to determine if 
                  the Condition clause in this ECA Policy Rule should be
                  evaluated or not. Examples include alarms and various 
                  device statistics (e.g., a type of threshold that was 
                  exceeded), which may signal the need for further 
                  action.";
                  
                leaf dev-sec-event-id {
                  type uint8;
                  mandatory true;
                  description
                    "The ID of the dev-sec-event.
                     This is key for dev-sec-event-list.
                     This must be unique.";
                }

                leaf dev-sec-event-content {
                  type string;
                  mandatory true;
                  description
                   "This is a mandatory string that contains the content 
                    of the DeviceSecurityEvent. The format of the 
                    content is specified in the devSecEventFormat class
                    attribute, and the type of event is defined in the 
                    devSecEventType class attribute. An example of the 
                    devSecEventContent attribute is alarm, with the 
                    devSecEventFormat attribute set to 1 (GUID), the 
                    devSecEventType attribute set to 5 (new logon).";
                }

                leaf dev-sec-event-format {
                  type sec-event-format;
                  mandatory true;
                  description
                   "This is a mandatory uint 8 enumerated integer, 
                    which is used to specify the data type of the 
                    devSecEventContent attribute.";
                }

                leaf dev-sec-event-type {
                  type enumeration {
                      enum unknown {
                          description
                            "If devSecEventType is unknown";
                      }
                      enum comm-alarm {
                          description
                            "If devSecEventType is communications 
                            alarm";
                      }
                      enum quality-of-service-alarm {
                          description
                            "If devSecEventType is quality of service 
                            alarm";
                      }
                      enum process-err-alarm {
                          description
                            "If devSecEventType is processing error 
                            alarm";
                      }
                      enum equipment-err-alarm {
                          description
                            "If devSecEventType is equipment error 
                            alarm";
                      }
                      enum environmental-err-alarm {
                          description
                            "If devSecEventType is environmental error 
                            alarm";
                      }
                  }
                  mandatory true;
                  description
                   "This is a mandatory uint 8 enumerated integer, 
                    which is used to specify the type of event 
                    that was generated by this device.";
                }

                leaf dev-sec-event-type-severity {
                  type enumeration {
                      enum unknown {
                          description
                            "If devSecEventType is unknown";
                      }
                      enum cleared {
                          description
                            "If devSecEventTypeSeverity is cleared";
                      }
                      enum indeterminate {
                          description
                            "If devSecEventTypeSeverity is 
                            indeterminate";
                      }
                      enum critical {
                          description
                            "If devSecEventTypeSeverity is critical";
                      }
                      enum major{
                          description
                            "If devSecEventTypeSeverity is major";
                      }
                      enum minor {
                          description
                            "If devSecEventTypeSeverity is minor";
                      }
                      enum warning {
                          description
                            "If devSecEventTypeSeverity is warning";
                      }

                  }
                  mandatory true;
                  description
                   "This is a mandatory uint 8 enumerated integer, 
                    which is used to specify the perceived 
                    severity of the event generated by this 
                    Device.";
                }               
              }
              
              list system-security-event {
                key sys-sec-event-id;
                description
                  "The purpose of a SystemSecurityEvent is to represent 
                   events that are detected by the management system, 
                   instead of events that are generated by a user or a 
                   device. Information in this event may be used as part 
                   of a test to determine if the Condition clause in 
                   this ECA Policy Rule should be evaluated or not. 
                   Examples include an event issued by an analytics 
                   system that warns against a particular pattern of 
                   unknown user accesses, or an event issued by a 
                   management system that represents a set of correlated 
                   and/or filtered events.";
                  
                leaf sys-sec-event-id {
                  type uint8;
                  mandatory true;
                  description
                    "The ID of the sys-sec-event.
                     This is key for sys-sec-event-list.
                     This must be unique.";
                }
                
                leaf sys-sec-event-content {
                  type string;
                  mandatory true;
                  description
                   "This is a mandatory string that contains a content 
                    of the SystemSecurityEvent. The format of a content 
                    is specified in a sysSecEventFormat class attribute,
                    and the type of event is defined in the 
                    sysSecEventType class attribute. An example of the 
                    sysSecEventContent attribute is string sysadmin3,
                    with the sysSecEventFormat attribute set to 1(GUID), 
                    and the sysSecEventType attribute set to 2 
                    (audit log cleared).";
                }
                
                leaf sys-sec-event-format {
                  type sec-event-format;
                  mandatory true;
                  description
                   "This is a mandatory uint 8 enumerated integer, which 
                    is used to specify the data type of the 
                    sysSecEventContent attribute.";
                }
                
                leaf sys-sec-event-type {
                  type enumeration {
                      enum unknown {
                          description
                            "If sysSecEventType is unknown";
                      }
                      enum audit-log-written-to {
                          description
                          "If sysSecEventTypeSeverity 
                           is that audit log is written to";
                      }
                      enum audit-log-cleared {
                          description
                          "If sysSecEventTypeSeverity 
                           is that audit log is cleared";
                      }
                      enum policy-created {
                          description
                          "If sysSecEventTypeSeverity 
                           is that policy is created";
                      }
                      enum policy-edited{
                          description
                          "If sysSecEventTypeSeverity 
                           is that policy is edited";
                      }
                      enum policy-deleted{
                          description
                          "If sysSecEventTypeSeverity 
                           is that policy is deleted";
                      }
                      enum policy-executed{
                          description
                          "If sysSecEventTypeSeverity 
                           is that policy is executed";
                      }
                }
                  mandatory true;
                  description
                   "This is a mandatory uint 8 enumerated integer, which 
                    is used to specify the type of event that involves 
                    this device.";
                }
              }
              
              list time-security-event {
                key time-sec-event-id;
                description
                "Purpose of a TimeSecurityEvent is to represent events
                 that are temporal in nature (e.g., the start or end of 
                 a period of time). Time events signify an individual 
                 occurrence, or a time period, in which a significant 
                 event happened. Information in the event may be used as 
                 part of a test to determine if the Condition clause in 
                 this ECA Rule should be evaluated or not. Examples 
                 include issuing an event at a specific time to indicate 
                 that a particular resource should not be accessed, or 
                 that different authentication and authorization 
                 mechanisms should now be used (e.g., because it is now 
                 past regular business hours).";

                leaf time-sec-event-id {
                  type uint8;
                  mandatory true;
                  description
                    "The ID of the time-sec-event.
                     This is key for time-sec-event-list.
                     This must be unique.";
                }
                
                leaf time-sec-event-period-begin {
                  type yang:date-and-time;
                  mandatory true;
                  description
                    "This is a mandatory DateTime attribute, and 
                    represents the beginning of a time period. 
                    It has a value that has a date and/or a time 
                    component (as in the Java or Python libraries).";
                }

                leaf time-sec-event-period-end {
                  type yang:date-and-time;
                  mandatory true;
                  description
                    "This is a mandatory DateTime attribute, and 
                     represents the end of a time period. It has 
                     a value that has a date and/or a time component
                     (as in the Java or Python libraries). If this is
                     a single event occurrence, and not a time period
                     when the event can occur, then the 
                     timeSecEventPeriodEnd attribute may be ignored.";
                }
                
                leaf time-sec-event-time-zone {
                  type string;
                  mandatory true;
                  description
                    "This is a mandatory string attribute, and defines a
                     time zone that this event occurred in using the 
                     format specified in ISO8601.";
                }
              }
          }

          container condition {
            description
              "TBD";
            container packet-security-condition {
              description
                "The purpose of this Class is to represent packet header 
                 information that can be used as part of a test to 
                 determine if the set of Policy Actions in this ECA 
                 Policy Rule should be executed or not. This class is 
                 abstract, and serves as the superclass of more detailed 
                 conditions that involve different types of packet 
                 formats.";

              container packet-security-mac-condition {
                description
                  "The purpose of this Class is to represent packet MAC
                   packet header information that can be used as part of
                   a test to determine if the set of Policy Actions in
                   this ECA Policy Rule should be execute or not.";

                leaf-list pkt-sec-cond-mac-dest {
                  type inet:port-number;
                  description
                    "The MAC destination address (6 octets long).";
                }

                leaf-list pkt-sec-cond-mac-src {
                  type inet:port-number;
                  description
                    "The MAC source address (6 octets long).";
                }

                leaf-list pkt-sec-cond-mac-8021q {
                  type string;
                  description
                    "This is an optional string attribute, and defines
                     The 802.1Q tab value (2 octets long).";
                }

                leaf-list pkt-sec-cond-mac-ether-type {
                  type string;
                  description
                    "The EtherType field (2 octets long). Values up to
                     and including 1500 indicate the size of the payload
                     in octets; values of 1536 and above define which
                     protocol is encapsulated in the payload of the
                     frame.";
                }

                leaf-list pkt-sec-cond-mac-tci {
                  type string;
                  description
                    "This is an optional string attribute, and defines
                     the Tag Control Information. This consists of a 3
                     bit user priority field, a drop eligible indicator
                     (1 bit), and a VLAN identifier (12 bits).";
                }
              }

              container packet-security-ipv4-condition {
                description
                  "The purpose of this Class is to represent packet IPv4
                   packet header information that can be used as part of
                   a test to determine if the set of Policy Actions in
                   this ECA Policy Rule should be executed or not.";

                leaf-list pkt-sec-cond-ipv4-header-length {
                  type uint8;
                  description
                    "The IPv4 packet header consists of 14 fields, 
                     of which 13 are required.";
                }

                leaf-list pkt-sec-cond-ipv4-tos {
                  type uint8;
                  description
                    "The ToS field could specify a datagram's priority
                     and request a route for low-delay, high-throughput,
                     or highly-reliable service..";
                }

                leaf-list pkt-sec-cond-ipv4-total-length {
                  type uint16;
                  description
                    "This 16-bit field defines the entire packet size,
                     including header and data, in bytes.";
                }

                leaf-list pkt-sec-cond-ipv4-id {
                  type uint8;
                  description
                    "This field is an identification field and is 
                     primarily used for uniquely identifying 
                     the group of fragments of a single IP datagram.";
                }

                leaf-list pkt-sec-cond-ipv4-fragment {
                  type uint8;
                  description
                    "IP fragmentation is an Internet Protocol (IP)
                     process that breaks datagrams into smaller pieces 
                     (fragments), so that packets may be formed that 
                     can pass through a link with a smaller maximum 
                     transmission unit (MTU) than the original 
                     datagram size.";
                }

                leaf-list pkt-sec-cond-ipv4-fragment-offset {
                  type uint16;
                  description
                    "Fragment offset field along with Don't Fragment 
                     and More Fragment flags in the IP protocol 
                     header are used for fragmentation and reassembly 
                     of IP datagrams.";
                } 

                leaf-list pkt-sec-cond-ipv4-ttl {
                  type uint8;
                  description
                    "The ttl keyword is used to check for a specific
                     IP time-to-live value in the header of 
                     a packet."; 
                }

                leaf-list pkt-sec-cond-ipv4-protocol {
                  type uint8;
                  description
                    "Internet Protocol version 4(IPv4) is the fourth
                     version of the Internet Protocol (IP).";
                }

                leaf-list pkt-sec-cond-ipv4-src {
                  type inet:ipv4-address;
                  description
                    "Defines the IPv4 Source Address.";
                }

                leaf-list pkt-sec-cond-ipv4-dest {
                  type inet:ipv4-address;
                  description
                    "Defines the IPv4 Destination Address.";
                }

                leaf pkt-sec-cond-ipv4-ipopts {
                  type string;
                  description
                    "With the ipopts keyword you can check if 
                     a specific ip option is set. Ipopts has 
                     to be used at the beginning of a rule."; 
                }

                leaf pkt-sec-cond-ipv4-sameip {
                  type boolean;
                  description
                    "Every packet has a source IP-address and 
                     a destination IP-address. It can be that 
                     the source IP is the same as 
                     the destination IP.";
                }

                leaf-list pkt-sec-cond-ipv4-geoip {
                  type string;
                  description
                    "The geoip keyword enables you to match on 
                     the source, destination or source and destination
                     IP addresses of network traffic and to see to
                     which country it belongs. To do this, Suricata 
                     uses GeoIP API with MaxMind database format.";
                }
              }
                
              container packet-security-ipv6-condition {
                description
                   "The purpose of this Class is to represent packet 
                   IPv6 packet header information that can be used as 
                   part of a test to determine if the set of Policy 
                   Actions in this ECA Policy Rule should be executed 
                   or not.";
                    
                leaf-list pkt-sec-cond-ipv6-dscp {
                  type string;
                  description
                    "Differentiated Services Code Point (DSCP) 
                     of ipv6.";
                }

                leaf-list pkt-sec-cond-ipv6-ecn {
                  type string;
                  description
                    "ECN allows end-to-end notification of network 
                     congestion without dropping packets.";
                }

                leaf-list pkt-sec-cond-ipv6-traffic-class {
                  type uint8;
                  description
                    "The bits of this field hold two values. The 6
                     most-significant bits are used for 
                     differentiated services, which is used to
                     classify packets.";
                }

                leaf-list pkt-sec-cond-ipv6-flow-label {
                  type uint32;
                  description
                    "The flow label when set to a non-zero value 
                     serves as a hint to routers and switches 
                     with multiple outbound paths that these 
                     packets should stay on the same path so that
                     they will not be reordered."; 
                }

                leaf-list pkt-sec-cond-ipv6-payload-length {
                  type uint16;
                  description
                    "The size of the payload in octets, 
                     including any extension headers.";
                }

                leaf-list pkt-sec-cond-ipv6-next-header {
                  type uint8;
                  description
                    "Specifies the type of the next header. 
                     This field usually specifies the transport 
                     layer protocol used by a packet's payload.";
                }

                leaf-list pkt-sec-cond-ipv6-hop-limit {
                  type uint8;
                  description
                    "Replaces the time to live field of IPv4.";
                }

                leaf-list pkt-sec-cond-ipv6-src {
                  type inet:ipv6-address;
                  description
                    "The IPv6 address of the sending node.";
                }

                leaf-list pkt-sec-cond-ipv6-dest {
                  type inet:ipv6-address;
                  description
                    "The IPv6 address of the destination node(s).";
                }
              }
                
              container packet-security-tcp-condition {
                description
                  "The purpose of this Class is to represent packet 
                   TCP packet header information that can be used as 
                   part of a test to determine if the set of Policy 
                   Actions in this ECA Policy Rule should be executed 
                   or not.";
                    
                leaf-list pkt-sec-cond-tcp-seq-num {
                  type uint32;
                  description
                    "If the SYN flag is set (1), then this is the
                     initial sequence number.";
                }

                leaf-list pkt-sec-cond-tcp-ack-num {
                  type uint32;
                  description
                    "If the ACK flag is set then the value of this 
                     field is the next sequence number that the sender
                     is expecting.";
                }

                leaf-list pkt-sec-cond-tcp-window-size {
                  type uint16;
                  description
                    "The size of the receive window, which specifies 
                     the number of windows size units (by default,bytes)
                     (beyond the segment identified by the sequence 
                     number in the acknowledgment field) that the sender
                     of this segment is currently willing to recive.";
                }

                leaf-list pkt-sec-cond-tcp-flags {
                  type uint8;
                  description
                    "This is a mandatory string attribute, and defines 
                     the nine Control bit flags (9 bits).";
                }
              }
                
              container packet-security-udp-condition {
                description
                  "The purpose of this Class is to represent packet UDP
                   packet header information that can be used as part 
                   of a test to determine if the set of Policy Actions 
                   in this ECA Policy Rule should be executed or not.";
                    
                leaf-list pkt-sec-cond-udp-length {
                  type string;
                  description
                    "This is a mandatory string attribute, and defines 
                     the length in bytes of the UDP header and data 
                     (16 bits).";
                }
              }

              container packet-security-icmp-condition {
                description
                  "The internet control message protocol condition.";

                leaf-list pkt-sec-cond-icmp-type {
                  type uint8;
                  description
                    "ICMP type, see Control messages.";
                }

                leaf-list pkt-sec-cond-icmp-code {
                  type uint8;
                  description
                    "ICMP subtype, see Control messages.";
                }

                leaf-list pkt-sec-cond-icmp-seg-num {
                  type uint32;
                  description
                    "The icmp Sequence Number.";
                }
              }
            }
            container packet-payload-security-condition {
                description
                  "The ID of the pkt-payload.
                   This is key for pkt-payload-list.
                   This must be unique.";
                
                leaf pkt-payload-content {
                  type string;
                  description
                    "The content keyword is very important in 
                     signatures. Between the quotation marks you
                     can write on what you would like the
                     signature to match.";
                }

                leaf pkt-payload-nocase {
                  type boolean;
                  description
                    "If you do not want to make a distinction 
                     between uppercase and lowercase characters,
                     you can use nocase.";
                }

                leaf pkt-payload-depth {
                  type uint32;
                  description
                    "The depth keyword is a absolute content 
                     modifier.";
                }

                leaf pkt-payload-offset {
                  type uint32;
                  description
                    "The offset keyword designates from which byte
                     in the payload will be checked to fined to find
                     a match.";
                }

                leaf pkt-payload-distance {
                  type uint32;
                  description
                    "The keyword distance is a relative content
                     modifier. This means it indicates a relation
                     between this content keyword and the content
                     preceding it.";
                }

                leaf pkt-payload-within {
                  type uint32;
                  description
                    "The keyword within is relative to the preceding
                     match. The keyword within comes with a mandatory
                     numeric value.";
                }

                leaf pkt-payload-isdataat {
                  type uint32;
                  description
                    "The purpose of the isdataat keyword is to 
                     look if there is still data at a specific part 
                     of the payload.";
                }

                leaf pkt-payload-dsize {
                  type uint32;
                  description
                    "With the dsize keyword, you can match on the
                     size of the packet payload.";
                }

                leaf pkt-payload-replace {
                  type string;
                  description
                    "The replace content modifier can only be used
                     in ips. It adjusts network traffic.";
                }

                leaf pkt-payload-pcre {
                  type string;
                  description
                    "For information about pcre check the pcre
                     (Perl Compatible Regular Expressions)page.";
                }

                container pkt-payload-rpc{
                  description
                    "The rpc keyword can be used to match in the
                     SUNRPC CALL on the RPC procedure numbers and
                     the RPC version.";

                  leaf pkt-payload-rpc-app-num {
                    type uint32;
                    description
                      "<application number>.";
                  }

                  leaf pkt-payload-rpc-version-num {
                    type uint32;
                    description
                      "<version number>|*."; 
                  }

                  leaf pkt-payload-rpc-procedure-num {
                    type uint32;
                    description
                      "<procedure number>|*.";
                  }
                }
              }
              container target-security-condition {
                description
                  "Under the circumstances of network, it mainly
                   refers to the service, application, and device.";

                container service-sec-context-cond{
                  description 
                    "A service is an application identified by a 
                     protocol type and port number, such as TCP, 
                     UDP, ICMP, and IP.";

                  container protocol {
                    description 
                      "Protocol types: 
                       TCP, UDP, ICMP, ICMPv6, IP, and etc.";

                    leaf tcp  {
                      type boolean;
                      description 
                        "TCP protocol type.";
                    }

                    leaf udp {
                      type boolean;
                      description
                        "UDP protocol type.";
                    }

                    leaf icmp {
                      type boolean;
                      description
                        "ICMP protocol type.";
                    }

                    leaf icmpv6 {
                      type boolean;
                      description 
                        "ICMPv6 protocol type.";
                    }

                    leaf ip {
                      type boolean;
                      description 
                        "IP protocol type.";
                    }
                  }

                  leaf-list src-port{
                    type int32;
                    description 
                      "It can be used for finding programs.";
                  }

                  leaf-list dest-port{
                    type int32;
                    description 
                      "It can be used for finding programs.";
                  }
                }

                container application-sec-context-cond {
                  description 
                    "An application is a computer program for 
                     a specific task or purpose. It provides 
                     a finer granularity than service in matching 
                     traffic.";

                  container category{
                    description 
                      "Category types: Business system, Entertainment, 
                       Interest, Network, General, and etc.";

                    leaf business-system {
                      type boolean;
                      description 
                        "Business system category.";
                    }

                    leaf entertainment {
                      type boolean;
                      description 
                        "Entertainment category.";
                    }

                    leaf interest {
                      type boolean;
                      description 
                        "Interest category.";
                    }

                    leaf network {
                      type boolean;
                      description 
                        "Network category.";
                    }

                    leaf general {
                      type boolean;
                      description 
                        "General category.";
                    }
                  }
                  container subcategory{
                    description 
                      "Subcategory types: Finance, Email, Game, 
                       Media sharing, Social network, Web posting, 
                       and etc.";

                    leaf finance {
                      type boolean;
                      description 
                        "Finance subcategory.";
                    }

                    leaf email {
                      type boolean;
                      description 
                        "Email subcategory.";
                    }

                    leaf game {
                      type boolean;
                      description 
                        "Game subcategory.";
                    }

                    leaf media-sharing {
                      type boolean;
                      description 
                        "Media sharing subcategory.";
                    }

                    leaf social-network {
                      type boolean;
                      description 
                        "Social network subcategory.";
                    }

                    leaf web-posting {
                      type boolean;
                      description 
                        "Web posting subcategory.";
                    }
                  }

                  container data-transmission-model{
                    description 
                      "Data transmission model types: Client-server, 
                       Browser-based, Networking, Peer-to-Peer, 
                       Unassigned, and etc.";

                    leaf client-server {
                      type boolean;
                      description 
                        "client-server data transmission model.";
                    }

                    leaf browser-based {
                      type boolean;
                      description 
                        "Browser-based data transmission model.";
                    }

                    leaf networking {
                      type boolean;
                      description 
                        "Networking data transmission model.";
                    }

                    leaf peer-to-peer {
                      type boolean;
                      description 
                        "Peer-to-Peer data transmission model.";
                    }

                    leaf unassigned {
                      type boolean;
                      description 
                        "Unassigned data transmission model.";
                    }
                  }
                  container risk-level{
                    description 
                      "Risk level types: Exploitable, 
                       Productivity loss, Evasive, Data loss, 
                       Malware vehicle, Bandwidth consuming, 
                       Tunneling, and etc.";

                    leaf exploitable {
                      type boolean;
                      description 
                        "Exploitable risk level.";
                    }

                    leaf productivity-loss {
                      type boolean;
                      description 
                        "Productivity loss risk level.";
                    }

                    leaf evasive {
                      type boolean;
                      description 
                        "Evasive risk level.";
                    }

                    leaf data-loss {
                      type boolean;
                      description 
                        "Data loss risk level.";
                    }

                    leaf malware-vehicle {
                      type boolean;
                      description 
                        "Malware vehicle risk level.";
                    }

                    leaf bandwidth-consuming {
                      type boolean;
                      description 
                        "Bandwidth consuming risk level.";
                    }

                    leaf tunneling {
                      type boolean;
                      description 
                        "Tunneling risk level.";
                    }
                  }
                }                   

                container device-sec-context-cond {
                  description 
                    "The device attribute that can identify a device,
                     including the device type (i.e., router, switch,
                     pc, ios, or android) and the device's owner as
                     well.";

                  leaf pc {
                    type boolean;
                    description 
                      "If type of a device is PC.";
                  }

                  leaf mobile-phone {
                    type boolean;
                    description 
                      "If type of a device is mobile-phone.";
                  }

                  leaf tablet {
                    type boolean;
                    description 
                      "If type of a device is tablet.";
                  }

                  leaf voip-volte-phone {
                    type boolean;
                    description 
                      "If type of a device is voip-volte-phone.";
                  }         
                }
              }

              list user-security-cond {
                key "usr-sec-cond-id";
                description
                  "TBD";

                leaf usr-sec-cond-id {
                  type uint8;
                  description
                    "The ID of the user-sec-cond.
                     This is key for user-sec-cond-list.
                     This must be unique.";
                }

                container user{
                  description 
                    "The user (or user group) information with which
                     network flow is associated: The user has many 
                     attributes such as name, id, password, type, 
                     authentication mode and so on. Name/id is often 
                     used in the security policy to identify the user.
                     Besides, NSF is aware of the IP address of the 
                     user provided by a unified user management system
                     via network. Based on name-address association,
                     NSF is able to enforce the security functions 
                     over the given user (or user group)";

                  choice user-name {
                    description 
                      "The name of the user.
                       This must be unique.";

                    case tenant {
                      description 
                        "Tenant information.";

                      leaf tenant {
                        type uint8;
                        mandatory true;
                        description 
                          "User's tenant information.";
                      }
                    }

                    case vn-id {
                      description 
                        "VN-ID information.";

                      leaf vn-id {
                        type uint8;
                        mandatory true;
                        description
                          "User's VN-ID information.";
                      }
                    }
                  }
                }
                container group {
                  description 
                    "The user (or user group) information with which
                     network flow is associated: The user has many 
                     attributes such as name, id, password, type, 
                     authentication mode and so on. Name/id is often 
                     used in the security policy to identify the user.
                     Besides, NSF is aware of the IP address of the 
                     user provided by a unified user management system
                     via network. Based on name-address association,
                     NSF is able to enforce the security functions 
                     over the given user (or user group)";

                  choice group-name {
                    description 
                      "The name of the user.
                       This must be unique.";

                    case tenant {
                      description 
                        "Tenant information.";

                      leaf tenant {
                        type uint8;
                        mandatory true;
                        description 
                          "User's tenant information.";
                      }
                    }

                    case vn-id {
                      description 
                        "VN-ID information.";

                      leaf vn-id {
                        type uint8;
                        mandatory true;
                        description
                          "User's VN-ID information.";
                      }
                    }
                  }
                }
              }

              container generic-context-condition {
                description
                  "TBD";
		
				container schedule {
					leaf start-time {
						type xs:time;
						description
						 "This is start time for time zone";
					}
					leaf end-time {
						type xs:time;
						description
						 "This is end time for time zone";

					}
				}

                container geographic-location {
                  description
                    "The location where network traffic is associated
                     with. The region can be the geographic location 
                     such as country, province, and city, 
                     as well as the logical network location such as 
                     IP address, network section, and network domain.";

                  leaf-list geographic-location {
                    type uint8;
                    description
                      "This is mapped to ip address. We can acquire 
                       region through ip address stored the database.";
                  }
                }
              } 
          }

          container action {
            description
              "TBD.";
            choice action-type {
            description 
              "The flow-based NSFs realize the network security 
               functions by executing various Actions, which at least
               includes ingress-action, egress-action, and 
               advanced-action.";

            case ingress-action {
              description 
                "The ingress actions consist of permit, deny,
                 and mirror.";

              leaf ingress-action-type {
                type ingress-action;
                description
                  "Ingress action type: permit, deny, and mirror.";
              }
            }  

            case egress-action {
              description
                "The egress actions consist of invoke-signaling, 
                tunnel-encapsulation, and forwarding.";

              leaf egress-action-type {
                type egress-action;
                description
                  "Egress-action-type: invoke-signaling,
                   tunnel-encapsulation, and forwarding.";
              }
            }

            case apply-profile-action {
              description 
                "Applying a specific Functional Profile or signature 
                 - e.g., an IPS Profile, a signature file, an 
                 anti-virus file, or a URL filtering file. The 
                 functional profile or signature file corresponds to
                 the security capability for the content security 
                 control and attack mitigation control which will be 
                 described afterwards. It is one of the key properties
                 that determine the effectiveness of the NSF, and is
                 mostly vendor specific today. One goal of I2NSF is 
                 to standardize the form and functional interface of 
                 those security capabilities while supporting vendor-
                 specific implementations of each.";

              choice apply-profile-action-type {
                description
                  "Advanced action types: Content Security Control 
                   and Attack Mitigation Control.";

                case content-security-control {
                  description
                    "Content security control is another category of 
                    security capabilities applied to application layer.
                    Through detecting the contents carried over the 
                    traffic in application layer, these capabilities
                    can realize various security purposes, such as 
                    defending against intrusion, inspecting virus, 
                    filtering malicious URL or junk email, and blocking 
                    illegal web access or data retrieval.";

                  container content-security-control-types {
                    description
                     "Content Security types: Antivirus, IPS, IDS, 
                      url-filtering, data-filtering, mail-filtering,
                      file-blocking, file-isolate, pkt-capture,
                      application-control, and voip-volte.";

                    leaf antivirus-insp {
                        type boolean;
                        description 
                          "Additional inspection of antivirus.";
                    }

                    leaf ips-insp {
                        type boolean;
                        description
                          "Additional inspection of IPS.";
                    }

                    leaf ids-insp {
                        type boolean;
                        description
                          "Additional inspection of IDS.";
                    }

                    leaf url-filtering-insp {
                        type boolean;
                        description 
                          "Additional inspection of URL filtering.";
                    }

                    leaf data-filtering-insp {
                       type boolean;
                       description 
                         "Additional inspection of data filtering.";
                    }

                    leaf mail-filtering-insp {
                      type boolean;
                      description 
                        "Additional inspection of mail filtering.";
                    }

                    leaf file-blocking-insp {
                      type boolean;
                      description 
                        "Additional inspection of file blocking.";
                    }

                    leaf file-isolate-insp {
                      type boolean;
                      description 
                        "Additional inspection of file isolate.";
                    }

                    leaf pkt-capture-insp {
                      type boolean;
                      description 
                        "Additional inspection of packet capture.";
                    }

                    leaf application-control-insp {
                      type boolean;
                      description 
                        "Additional inspection of app control.";
                    }

                    leaf voip-volte-insp {
                      type boolean;
                      description 
                        "Additional inspection of VoIP/VoLTE.";
                    }
                  }
                }

                case attack-mitigation-control {
                  description
                    "This category of security capabilities is 
                     specially used to detect and mitigate various
                     types of network attacks.";

                  choice attack-mitigation-control-type {
                    description
                      "Attack-mitigation types: DDoS-attack and 
                       Single-packet attack.";

                    case ddos-attack {
                      description
                        "A distributed-denial-of-service (DDoS) is 
                         where the attack source is more than one, 
                         often thousands of unique IP addresses.";

                      container ddos-attack-type {
                        description
                          "DDoS-attack types: Network Layer DDoS Attacks 
                           and Application Layer DDoS Attacks.";

                        container network-layer-ddos-attack {
                          description
                            "Network layer DDoS-attack.";
                          container network-layer-ddos-attack-types {
                            description
                              "Network layer DDoS attack types: 
                               Syn Flood Attack, UDP Flood Attack,
                               ICMP Flood Attack, IP Fragment Flood, 
                               IPv6 Related Attacks, and etc";

                            leaf syn-flood-insp {
                              type boolean;
                              description
                                "Additional Inspection of 
                                 Syn Flood Attack.";
                            }

                            leaf udp-flood-insp {
                              type boolean;
                              description
                                "Additional Inspection of 
                                 UDP Flood Attack.";
                            }

                            leaf icmp-flood-insp {
                              type boolean;
                              description
                                "Additional Inspection of 
                                 ICMP Flood Attack.";
                            }

                            leaf ip-frag-flood-insp {
                              type boolean;
                              description
                                "Additional Inspection of 
                                 IP Fragment Flood.";
                            }

                            leaf ipv6-related-insp {
                              type boolean;
                              description
                                "Additional Inspection of 
                                 IPv6 Related Attacks.";
                            }
                          }
                        }

                        container app-layer-ddos-attack {
                          description
                            "Application layer DDoS-attack.";

                          container app-ddos-attack-types {
                            description
                              "Application layer DDoS-attack types: 
                               Http Flood Attack, Https Flood Attack, 
                               DNS Flood Attack, and 
                               DNS Amplification Flood Attack,
                               SSL DDoS Attack, and etc.";

                            leaf http-flood-insp {
                              type boolean;
                              description
                                "Additional Inspection of 
                                 Http Flood Attack.";
                            }

                            leaf https-flood-insp {
                              type boolean;
                              description
                                "Additional Inspection of 
                                 Https Flood Attack.";
                            }

                            leaf dns-flood-insp {
                              type boolean;
                              description
                                "Additional Inspection of 
                                 DNS Flood Attack.";
                            }

                            leaf dns-amp-flood-insp {
                              type boolean;
                              description
                                "Additional Inspection of 
                                 DNS Amplification Flood Attack.";
                            }

                            leaf ssl-ddos-insp {
                              type boolean;
                              description
                                "Additional Inspection of 
                                 SSL Flood Attack.";
                            }
                          }
                        }
                      }
                    }

                    case single-packet-attack {
                      description
                        "Single Packet Attacks.";
                      container single-packet-attack-type {
                        description
                          "DDoS-attack types: Scanning Attack, 
                           Sniffing Attack, Malformed Packet Attack,
                           Special Packet Attack, and etc.";

                        container scan-and-sniff-attack {
                          description
                            "Scanning and Sniffing Attack.";
                          container scan-and-sniff-attack-types {
                            description
                              "Scanning and sniffing attack types: 
                               IP Sweep attack, Port Scanning, 
                               and etc.";

                            leaf ip-sweep-insp {
                              type boolean;
                              description
                                "Additional Inspection of 
                                 IP Sweep Attack.";
                            }

                            leaf port-scanning-insp {
                              type boolean;
                              description
                                "Additional Inspection of 
                                 Port Scanning Attack.";
                            }
                          }
                        }

                        container malformed-packet-attack {
                          description
                            "Malformed Packet Attack.";
                          container malformed-packet-attack-types {
                            description
                              "Malformed packet attack types: 
                               Ping of Death Attack, Teardrop Attack, 
                               and etc.";

                            leaf ping-of-death-insp {
                              type boolean;
                              description
                                "Additional Inspection of 
                                 Ping of Death Attack.";
                            }

                            leaf teardrop-insp {
                              type boolean;
                              description
                                "Additional Inspection of 
                                 Teardrop Attack.";
                            }
                          }
                        }

                        container special-packet-attack {
                          description
                            "special Packet Attack.";
                          container special-packet-attack-types {
                            description
                              "Special packet attack types: 
                               Oversized ICMP Attack, Tracert Attack,
                               and etc.";

                            leaf oversized-icmp-insp {
                              type boolean;
                              description
                                "Additional Inspection of 
                                 Oversize ICMP Attack.";
                            }

                            leaf tracert-insp {
                              type boolean;
                              description
                                "Additional Inspection of 
                                 Tracrt Attack.";
                            }
                          }
                        }
                      }
                    }
                  }
                }
              }
            }
          } 
      }
    }
  }
 }

 container cfg-content-security-control {
  description
    "Configuration for Content Security Control.";

  choice cfg-content-security-control-type {
    description
      "Content Security types: Antivirus, IPS, IDS, 
       url-filtering, data-filtering, mail-filtering,
       file-blocking, file-isolate, pkt-capture,
       application-control, and voip-volte.";

    case cfg-antivirus {
      description
        "Antivirus Case.";

      list antivirus-rule {
        key rule-id;
        description
          "Rule of Antivirus.";

        leaf rule-id {
          type uint8;
          mandatory true;
          description
            "The ID of the rule about antivirus.";
        }
      }
    }

    case cfg-ips {
      description
        "IPS Case.";

      list ips-rule {
        key rule-id;
        description
          "Rule of IPS.";

        leaf rule-id {
          type uint8;
          mandatory true;
          description
            "The ID of the rule about IPS.";
        }
      }
    }

    case cfg-ids {
      description
        "IDS Case.";

      list ids-rule {
        key rule-id;
        description
          "Rule of IDS.";

        leaf rule-id {
          type uint8;
          mandatory true;
          description
            "The ID of the rule about IDS.";
        }
      }
    }

    case cfg-url-filter {
      description
        "URL Filter Case.";

      list url-filter-rule {
        key rule-id;
        description
          "Rule of URL filter.";

        leaf rule-id {
          type uint8;
          mandatory true;
          description
            "The ID of the rule about URL filter.";
        }
      }
    }

    case cfg-data-filter {
      description
        "Data Filter Case.";

      list data-filter-rule {
        key rule-id;
        description
          "Rule of Data Filter.";

        leaf rule-id {
          type uint8;
          mandatory true;
          description
            "The ID of the rule about data filter.";
        }
      }
    }

    case cfg-mail-filter {
      description
        "Mail Filter Case.";

      list mail-filter-rule {
        key rule-id;
        description
          "Rule of Mail Filter.";

        leaf rule-id {
          type uint8;
          mandatory true;
          description
            "The ID of the rule about mail filter.";
        }
      }
    }

    case cfg-file-blocking {
      description
        "File Blocking Case.";

      list file-blocking-rule {
        key rule-id;
        description
          "Rule of File Blocking.";

        leaf rule-id {
          type uint8;
          mandatory true;
          description
            "The ID of the rule about file blocking.";
        }
      }
    }

    case cfg-file-isolate {
      description
        "File Isolate Case.";

      list file-isolate-rule {
        key rule-id;
        description
          "Rule of File Isolate.";

        leaf rule-id {
          type uint8;
          mandatory true;
          description
            "The ID of the rule about file isolate.";
        }
      }
    }

    case cfg-pkt-capture {
      description
        "Packet Capture Case.";

      list pkt-capture-rule {
        key rule-id;
        description
          "Rule of Packet Capture.";

        leaf rule-id {
          type uint8;
          mandatory true;
          description
            "The ID of the rule about pacekt capture.";
        }
      }
    }

    case cfg-app-control {
      description
        "App Control Case.";

      list app-control-rule {
        key rule-id;
        description
          "Rule of App Control.";

        leaf rule-id {
          type uint8;
          mandatory true;
          description
            "The ID of the rule about app control.";
        }
      }
    }

    case cfg-voip-volte {
      description
       "VoIP/VoLTE Case.";

      list voip-volte-rule {
        key "rule-id";
        description 
          "For the VoIP/VoLTE security system, a VoIP/
           VoLTE security system can monitor each 
           VoIP/VoLTE flow and manage VoIP/VoLTE 
           security rules controlled by a centralized
           server for VoIP/VoLTE security service 
           (called VoIP IPS). The VoIP/VoLTE security 
           system controls each switch for the 
           VoIP/VoLTE call flow management by 
           manipulating the rules that can be added, 
           deleted, or modified dynamically.";

        leaf rule-id {
           type uint8;
           mandatory true;
           description
             "The ID of the voip-volte-rule.
              This is the key for voip-volte-rule-list.
              This must be unique.";
        } 

        container event { 
          description
            "Event types: VoIP and VoLTE.";

          leaf called-voip {
            type boolean;
            mandatory true;
            description
              "If content-security-control-type is
               voip.";
          }

          leaf called-volte {
            type boolean;
            mandatory true;
            description
               "If content-security-control-type is 
                volte.";
          }
        }

        container condition { 
          description
            "TBD.";

          list sip-header {
            key "sip-header-uri";
            description
              "TBD.";

            leaf sip-header-uri {
              type string;
              mandatory true;
              description
                "SIP header URI.";
            }

            leaf sip-header-method {
              type string;
              mandatory true;
              description
                "SIP header method.";
            }

            leaf sip-header-expire-time {
              type yang:date-and-time;
              mandatory true;
              description
                "SIP header expire time.";
             }

             leaf sip-header-user-agent {
               type uint32;
               mandatory true;
               description
                 "SIP header user agent.";
             }
           }

           list cell-region {
             key "cell-id-region";
             description
               "TBD.";

             leaf cell-id-region {
               type uint32;
               mandatory true;
               description
                 "Cell region.";
             }
           }
         }

         container action { 
            description
              "The flow-based NSFs realize the security 
               functions by executing various Actions.";

               choice action-type {
                  description
                    "Action type: ingress action and 
                     egress action.";

                  case ingress-action {
                     description 
                        "The ingress actions consist of permit,
                         deny, and mirror.";

                     leaf ingress-action-type {
                        type ingress-action; 
                        description
                           "Ingress-action-type: permit, deny,
                            and mirror.";
                    }
                  }

                  case egress-action {
                     description 
                        "The engress actions consist of 
                         mirror and etc.";

                     leaf egress-action-type {
                         type egress-action;
                         description
                            "Engress-action-type: redirection, 
                             and etc.";
                    }
                  }
               }
         }
      }
    }
  }
 }

 container cfg-attack-mitigation-control {
  description
    "Configuration for Attack Mitigation Control.";

  choice cfg-attack-mitigation-control-type {
     description
       "Attack-mitigation types: DDoS-attack and 
        Single-packet attack.";

     case cfg-ddos-attack {
       description
         "A distributed-denial-of-service (DDoS) is 
          where the attack source is more than one, 
          often thousands of unique IP addresses.";

       choice cfg-ddos-attack-type {
         description
           "DDoS-attack types: Network Layer DDoS Attacks 
            and Application Layer DDoS Attacks.";

         case cfg-network-layer-ddos-attack {
            description
               "Network layer DDoS-attack.";

            choice cfg-network-layer-ddos-attack-type {
                description
                   "Network layer DDoS attack types: 
                    Syn Flood Attack, UDP Flood Attack,
                    ICMP Flood Attack, IP Fragment Flood, 
                    IPv6 Related Attacks, and etc.";

               case cfg-syn-flood-attack {
                  description
                    "Syn Flood Attack Case.";

                  list syn-flood-attack-rule {
                    key rule-id;
                    description
                      "Rule of Syn Flood Attack.";

                    leaf rule-id {
                      type uint8;
                      mandatory true;
                      description
                        "The ID of the rule about syn flood attack.";
                    }
                  }
               }

               case cfg-udp-flood-attack {
                  description
                    "UDP Flood Attack Case.";

                  list udp-flood-attack-rule {
                    key rule-id;
                    description
                      "Rule of UDP Flood Attack.";

                    leaf rule-id {
                      type uint8;
                      mandatory true;
                      description
                        "The ID of the rule about udp flood attack.";
                    }
                  }
               }

               case cfg-icmp-flood-attack {
                  description
                    "ICMP Flood Attack Case.";

                  list icmp-flood-attack-rule {
                    key rule-id;
                    description
                      "Rule of ICMP Flood Attack.";

                    leaf rule-id {
                      type uint8;
                      mandatory true;
                      description
                        "The ID of the rule about icmp flood attack.";
                    }
                  }
               }

               case cfg-ip-frag-flood-attack {
                  description
                    "IP Fragment Flood Attack Case.";

                  list ip-frag-flood-attack-rule {
                    key rule-id;
                    description
                      "Rule of Ip Fragment Flood Attack.";

                    leaf rule-id {
                      type uint8;
                      mandatory true;
                      description
                        "The ID of the rule about 
                         ip fragment flood attack.";
                    }
                  }
               }

               case cfg-ipv6-related-attacks {
                  description
                    "IPv6 Related Attacks Case.";

                  list ipv6-related-attacks-rule {
                    key rule-id;
                    description
                      "Rule of Ipv6 Related Attacks.";

                    leaf rule-id {
                      type uint8;
                      mandatory true;
                      description
                        "The ID of the rule about 
                         ipv6 related attacks.";
                    }
                  }
               }
            }
         }

         case cfg-app-layer-ddos-attack {
            description
              "Application layer DDoS-attack.";

            choice cfg-app-ddos-attack-type {
               description
                 "Application layer DDoS-attack types: 
                  Http Flood Attack, Https Flood Attack, 
                  DNS Flood Attack, and 
                  DNS Amplification Flood Attack,
                  SSL DDoS Attack, and etc.";

               case cfg-http-flood-attack {
                  description
                    "HTTP Flood Attack Case.";

                  list http-flood-attack-rule {
                    key rule-id;
                    description
                      "Rule of HTTP Flood Attack.";

                    leaf rule-id {
                      type uint8;
                      mandatory true;
                      description
                        "The ID of the rule about 
                         http flood attack.";
                    }
                  }
               }

               case cfg-https-flood-attack {
                  description
                    "HTTPs Flood Attack Case.";

                  list https-flood-attack-rule {
                    key rule-id;
                    description
                      "Rule of HTTPs Flood Attack.";

                    leaf rule-id {
                      type uint8;
                      mandatory true;
                      description
                        "The ID of the rule about 
                         https flood attack.";
                    }
                  }
               }

               case cfg-dns-flood-attack {
                  description
                    "DNS Flood Attack Case.";

                  list dns-flood-attack-rule {
                    key rule-id;
                    description
                      "Rule of DNS Flood Attack.";

                    leaf rule-id {
                      type uint8;
                      mandatory true;
                      description
                        "The ID of the rule about 
                         dns flood attack.";
                    }
                  }
               }

               case cfg-dns-amp-flood-attack {
                  description
                    "DNS Amp Flood Attack Case.";

                  list dns-amp-flood-attack-rule {
                    key rule-id;
                    description
                      "Rule of DNS Amp Flood Attack.";

                    leaf rule-id {
                      type uint8;
                      mandatory true;
                      description
                        "The ID of the rule about 
                         dns amp flood attack.";
                    }
                  }
               }

               case cfg-ssl-ddos-attack {
                  description
                    "SSL DDoS Attack Case.";

                  list ssl-ddos-attack-rule {
                    key rule-id;
                    description
                      "Rule of SSL DDoS Attack.";

                    leaf rule-id {
                      type uint8;
                      mandatory true;
                      description
                        "The ID of the rule about 
                         ssl ddos attack.";
                    }
                  }
               }
            }
         }
      }
    }

    case cfg-single-packet-attack {
      description
        "Single Packet Attacks.";

      choice cfg-single-packet-attack-type {
        description
          "DDoS-attack types: Scanning Attack, 
           Sniffing Attack, Malformed Packet Attack,
           Special Packet Attack, and etc.";

        case cfg-scan-and-sniff-attack {
           description
             "Scanning and Sniffing Attack.";

           choice cfg-scan-and-sniff-attack-type {
              description
                 "Scanning and sniffing attack types: 
                  IP Sweep attack, Port Scanning, 
                  and etc.";

              case cfg-ip-sweep-attack {
                 description
                   "IP Sweep Attack Case.";

                 list ip-sweep-attack-rule {
                   key rule-id;
                   description
                     "Rule of IP Sweep Attack.";

                   leaf rule-id {
                     type uint8;
                     mandatory true;
                     description
                       "The ID of the rule about 
                        ip sweep attack.";
                   }
                 }
              }

              case cfg-port-scanning-attack {
                 description
                   "Port Scanning Attack Case.";

                 list port-scanning-attack-rule {
                   key rule-id;
                   description
                     "Rule of Port Scanning Attack.";

                   leaf rule-id {
                     type uint8;
                     mandatory true;
                     description
                       "The ID of the rule about 
                        port scanning attack.";
                   }
                 }
              }
           }
        }

        case cfg-malformed-packet-attack {
           description
             "Malformed Packet Attack.";

           choice cfg-malformed-packet-attack-type {
             description
               "Malformed packet attack types: 
                Ping of Death Attack, Teardrop Attack, 
                and etc.";

              case cfg-ping-of-death-attack {
                 description
                   "Ping of Death Attack Case.";

                 list ping-of-death-attack-rule {
                   key rule-id;
                   description
                     "Rule of Ping of Death Attack.";

                   leaf rule-id {
                     type uint8;
                     mandatory true;
                     description
                       "The ID of the rule about 
                        ping of death attack.";
                   }
                 }
              }

              case cfg-teardrop-attack {
                 description
                   "Teardrop Attack Case.";

                 list teardrop-attack-rule {
                   key rule-id;
                   description
                     "Rule of Teardrop Attack.";

                   leaf rule-id {
                     type uint8;
                     mandatory true;
                     description
                       "The ID of the rule about 
                        teardrop attack.";
                   }
                 }
              }
           }
        }

        case cfg-special-packet-attack {
           description
              "special Packet Attack.";

           choice cfg-special-packet-attack-type {
               description
                 "Special packet attack types: 
                  Oversized ICMP Attack, Tracert Attack,
                  and etc.";

               case cfg-oversized-icmp-attack {
                 description
                   "Oversized ICMP Attack Case.";

                 list oversized-icmp-attack-rule {
                   key rule-id;
                   description
                     "Rule of Oversized ICMP Attack.";

                   leaf rule-id {
                     type uint8;
                     mandatory true;
                     description
                       "The ID of the rule about 
                        oversized icmp attack.";
                   }
                 }
               }

               case cfg-tracert-attack {
                 description
                   "Tracert Attack Case.";

                 list tracert-attack-rule {
                   key rule-id;
                   description
                     "Rule of Tracert Attack.";

                   leaf rule-id {
                     type uint8;
                     mandatory true;
                     description
                       "The ID of the rule about 
                        tracert attack.";
                   }
                 }
              }
           }
         }
      }
    }
  }
 }
}
